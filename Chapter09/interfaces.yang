module interfaces {
	yang-version "1";
	namespace "http://netdevops.cn/yang/configuration/interfaces";
	prefix "nc-if";

    revision 2017-10-30 {
    	description
    	   "interface test";
    }

    typedef ipv4-address-prefix {
    	type string {
    		pattern '^(([0-9]|[1-9][0-9]|1[0-9][0-9]|2[0-4][0-9]|'  +
              '25[0-5])\.){3}([0-9]|[1-9][0-9]|1[0-9][0-9]|2[0-4]'  +
              '[0-9]|25[0-5])/(([0-9])|([1-2][0-9])|(3[0-2]))$';
     	}
    	description 
        	"ipv4-address";
       }
     
    
    
        list interface {
        	key "name";
        	leaf unit {
        		type int16 {
        			range "0 .. 16384";
        		}

        	}

        	leaf name {
        		type string;
        	}

        	leaf description {
        		type string {
        			length "1 .. 255";
        		}
        	}

            leaf mtu {
            	type int16 {
            		range "64 .. 9200";
            	}
            }



        	container family {
        		container inet {
        			container filter {
        				leaf-list input-list {
        					type string ;

        				}
        			}
        			list address {
        				key "name";
        				leaf name {
        				type ipv4-address-prefix;
        			   }
        			}
        		}
        	}
        }
    

}
